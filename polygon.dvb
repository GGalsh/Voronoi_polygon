Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True

Public Sub Project1()
Dim a As String, b As String, j As Double, i As Double
Dim Count As Double
Count = 0
Dim Point(0 To 2) As Double
Dim Points() As Variant


'导入数据
Open "D:\学习\研究生\研一上\GIS空间分析与建模\Project1\2672.txt" For Input As #1 '
Do While Not EOF(1)
Count = Count + 1
  If Count Mod 2 = 0 Then
    ReDim Preserve Points(Count / 2 - 1)
    Line Input #1, a
    For i = 0 To 2
      Point(i) = Val(Split(a, ",")(i + 1))
    Next
    Points(Count / 2 - 1) = Point
  Else
    Line Input #1, b
  End If
Loop
Close #1
Count = Count / 2
'绘制point图层
ret = Draw1("point")
Dim Get_Point(0 To 2) As Double
For i = 0 To Count - 1
  Get_Point(0) = Points(i)(0)
  Get_Point(1) = Points(i)(1)
  Get_Point(2) = Points(i)(2)
  ThisDrawing.ModelSpace.AddPoint Get_Point()
Next


'找到第一条边
Dim min_s As Double, Line_() As Variant, Square() As Variant, G_line(0 To 2) As Double, G_Square(0 To 2) As Double
'G_line:0边号，1起点点号，2终点点号
'G_Square：0，1，2三角形的三条边边号
Dim x1 As Double, x2 As Double, y1 As Double, y2 As Double, x3 As Double, y3 As Double
x1 = Points(0)(0): x2 = Points(1)(0): y1 = Points(0)(1): y2 = Points(1)(1)
min_s = Dianju(x1, x2, y1, y2)
For i = 0 To Count - 1
  For j = i + 1 To Count - 1
  x1 = Points(i)(0): x2 = Points(j)(0): y1 = Points(i)(1): y2 = Points(j)(1)
  If min_s > Dianju(x1, x2, y1, y2) Then
    min_s = Dianju(x1, x2, y1, y2)
    G_line(0) = 1
    G_line(1) = i
    G_line(2) = j
  End If
  Next
Next
ReDim Preserve Line_(0)
Line_(0) = G_line: j = 0
ReDim Preserve Square(j)
ReDim Preserve Line_(2 * j + 1)
ReDim Preserve Line_(2 * j + 2)
Dim a1, b1, c1, Cosata As Double
Dim G_jishu As Double, Square_P() As Variant, G_Square_P(0 To 2) As Double
ReDim Preserve Square_P(j)
Cosata = 1
x1 = Points(Line_(j)(1))(0): x2 = Points(Line_(j)(2))(0): y1 = Points(Line_(j)(1))(1): y2 = Points(Line_(j)(2))(1)
c1 = Dianju(x1, x2, y1, y2)
For i = 0 To Count - 1
  x3 = Points(i)(0): y3 = Points(i)(1)
  a1 = Dianju(x1, x3, y1, y3): b1 = Dianju(x2, x3, y2, y3)
  If 2 * a1 * b1 <> 0 Then
  If Cosata > (a1 * a1 + b1 * b1 - c1 * c1) / (2 * a1 * b1) And (a1 * a1 + b1 * b1 - c1 * c1) / (2 * a1 * b1) <> -1 Then
    Cosata = (a1 * a1 + b1 * b1 - c1 * c1) / (2 * a1 * b1)
    G_jishu = i
  End If
  End If
Next
G_line(0) = 2 * j + 2: G_line(1) = Line_(j)(1): G_line(2) = G_jishu: Line_(2 * j + 1) = G_line
G_line(0) = 2 * j + 3: G_line(1) = Line_(j)(2): G_line(2) = G_jishu: Line_(2 * j + 2) = G_line
G_Square(0) = j: G_Square(1) = (2 * j + 1): G_Square(2) = (2 * j + 2): Square(j) = G_Square
G_Square_P(0) = Line_(j)(1): G_Square_P(1) = Line_(j)(2): G_Square_P(2) = G_jishu: Square_P(j) = G_Square_P
j = j + 1
  
Dim g(0 To 1) As Double, jj As Double
i = 0: jj = 0: ii = 0
'进行循环三角增长
While (i <= 2 * j - jj)
  G_jishu = BIjiaoAngel(Points, Line_, Square, Square_P, i, j - 1, Count)
  If G_jishu = -1 Then
    
  ElseIf G_jishu = -2 Then
  ii = ii + 1
  Else
    ReDim Preserve Square(j)
    ReDim Preserve Square_P(j)
    g(0) = g1(Points, Line_, G_jishu, i, j, jj)(0)
    g(1) = g1(Points, Line_, G_jishu, i, j, jj)(1)
    If g(0) <> -1 Then
      jj = jj + 1
      G_Square(1) = g(0)
    Else
      ReDim Preserve Line_(2 * j + 1 - jj)
      G_line(0) = 2 * j + 2 - jj: G_line(1) = Line_(i)(1): G_line(2) = G_jishu: Line_(2 * j + 1 - jj) = G_line
      G_Square(1) = (2 * j + 1 - jj)
    End If
    If g(1) <> -1 Then
      jj = jj + 1
      G_Square(2) = g(1)
    Else
      ReDim Preserve Line_(2 * j + 2 - jj)
      G_line(0) = 2 * j + 3 - jj: G_line(1) = Line_(i)(2): G_line(2) = G_jishu: Line_(2 * j + 2 - jj) = G_line
      G_Square(2) = (2 * j + 2 - jj)
    End If
    G_Square(0) = i: Square(j) = G_Square
    G_Square_P(0) = Line_(i)(1): G_Square_P(1) = Line_(i)(2): G_Square_P(2) = G_jishu: Square_P(j) = G_Square_P
    j = j + 1
  End If
  i = i + 1
Wend

'绘制三角网的面
'绘制face图层
ret = Draw1("face")
Dim Point1(0 To 2) As Double, Point2(0 To 2) As Double, Point3(0 To 2) As Double
For k = 0 To j - 1
 Point1(0) = Points(Square_P(k)(0))(0): Point1(1) = Points(Square_P(k)(0))(1): Point1(2) = Points(Square_P(k)(0))(2)
 Point2(0) = Points(Square_P(k)(1))(0): Point2(1) = Points(Square_P(k)(1))(1): Point2(2) = Points(Square_P(k)(1))(2)
 Point3(0) = Points(Square_P(k)(2))(0): Point3(1) = Points(Square_P(k)(2))(1): Point3(2) = Points(Square_P(k)(2))(2)
 Set face = ThisDrawing.ModelSpace.Add3DFace(Point1, Point2, Point3, Point1)
Next
'将数组输出到txt文件
FileName = "D:\学习\研究生\研一上\GIS空间分析与建模\Project1\line_point.txt"
Open FileName For Output As #2
For k = 0 To i - 1
  Write #2, k + 1, Line_(k)(0), Line_(k)(1), Line_(k)(2)
Next
Close #2
FileName = "D:\学习\研究生\研一上\GIS空间分析与建模\Project1\Square_point.txt"
Open FileName For Output As #3
For k = 0 To j - 1
  Write #3, k + 1, Square_P(k)(0), Square_P(k)(1), Square_P(k)(2)
Next
Close #3
FileName = "D:\学习\研究生\研一上\GIS空间分析与建模\Project1\Square_line.txt"
Open FileName For Output As #4
For k = 0 To j - 1
  Write #4, k + 1, Square(k)(0), Square(k)(1), Square(k)(2)
Next
Close #4
'Square储存线号
'j三角形数目
ReDim Center_p(0 To j - 1) As Variant, Center(0 To 1) As Double
'计算每一个三角形的外心Center_p
For k = 0 To j - 1
  x1 = Points(Square_P(k)(0))(0): y1 = Points(Square_P(k)(0))(1)
  x2 = Points(Square_P(k)(1))(0): y2 = Points(Square_P(k)(1))(1)
  x3 = Points(Square_P(k)(2))(0): y3 = Points(Square_P(k)(2))(1)
  Center(0) = Waixin(x1, y1, x2, y2, x3, y3)(0)
  Center(1) = Waixin(x1, y1, x2, y2, x3, y3)(1)
  Center_p(k) = Center
Next
Dim Coll As New AcadAcCmColor
Coll.SetRGB 255, 0, 0
'绘制Voronoi图层
ret = Draw1("Voronoi")
Dim lineg(0 To 5) As Double
For k = 0 To j - 1
  For kk = k + 1 To j - 1
  '判断三角形有无共同边—若有-连接三角形外心
  If Square(k)(0) = Square(kk)(0) Or Square(k)(0) = Square(kk)(1) Or Square(k)(0) = Square(kk)(2) Or Square(k)(1) = Square(kk)(0) Or Square(k)(1) = Square(kk)(1) Or Square(k)(1) = Square(kk)(2) Or Square(k)(2) = Square(kk)(0) Or Square(k)(2) = Square(kk)(1) Or Square(k)(2) = Square(kk)(2) Then
     lineg(0) = Center_p(k)(0): lineg(1) = Center_p(k)(1): lineg(2) = 0
     lineg(3) = Center_p(kk)(0): lineg(4) = Center_p(kk)(1): lineg(5) = 0
     Set Line10 = ThisDrawing.ModelSpace.AddPolyline(lineg)
     Line10.TrueColor = Coll
  End If
  Next
Next

'绘制三角网
ret = Draw1("line")
ReDim GetPoint(0 To 5) As Double
For j = 0 To i - 1
GetPoint(0) = Points(Line_(j)(1))(0): GetPoint(1) = Points(Line_(j)(1))(1): GetPoint(2) = Points(Line_(j)(1))(2)
GetPoint(3) = Points(Line_(j)(2))(0): GetPoint(4) = Points(Line_(j)(2))(1): GetPoint(5) = Points(Line_(j)(2))(2)
Set Line1 = ThisDrawing.ModelSpace.AddPolyline(GetPoint)
Next
ZoomExtents
End Sub
Public Function Waixin(x1 As Double, y1 As Double, x2 As Double, y2 As Double, x3 As Double, y3 As Double)
'计算三角形外心
 Dim a, b, c, m, n, g As Double
 Dim g1(0 To 1) As Double
 a = x1 * x1 + y1 * y1
 b = x2 * x2 + y2 * y2
 c = x3 * x3 + y3 * y3
 g = (y3 - y2) * x1 + (y1 - y3) * x2 + (y2 - y1) * x3
 m = ((b - c) * y1 + (c - a) * y2 + (a - b) * y3) / (2 * g)
 n = ((c - b) * x1 + (a - c) * x2 + (b - a) * x3) / (2 * g)
 g1(0) = m: g1(1) = n
 Waixin = g1
End Function
Public Function Dianju(x1 As Double, x2 As Double, y1 As Double, y2 As Double)
'计算两点之间距离
  Dianju = Sqr((x1 - x2) * (x1 - x2) + (y1 - y2) * (y1 - y2))
End Function
Public Function g1(Point() As Variant, Line1() As Variant, Jishu As Double, a As Double, b As Double, jj As Double)
'判断新生成的边是否已经存在
  Dim g(0 To 1) As Double
  g(0) = -1: g(1) = -1
  For i = 0 To 2 * b - jj
    If Line1(i)(1) = Jishu Or Line1(i)(2) = Jishu Then
      If Line1(i)(1) = Line1(a)(1) Or Line1(i)(2) = Line1(a)(1) Then
        g(0) = i
      ElseIf Line1(i)(1) = Line1(a)(2) Or Line1(i)(2) = Line1(a)(2) Then
        g(1) = i
'本应该新生成的边存在于第i条边
      End If
    End If
  Next
  g1 = g
End Function
Public Function BIjiaoAngel(Point() As Variant, Line1() As Variant, Square As Variant, Square_P As Variant, a As Double, b As Double, Count As Double)
'比较角大小,返回角最大时c点的点号a为待算边的号数，b为三角形数目
Dim a1, b1, c1, Cosata As Double, IsEXit As Double
Dim Isline(0 To 2) As Double
Cosata = 1: BIjiaoAngel = 0: IsEXit = 0
Dim x1 As Double, x2 As Double, y1 As Double, y2 As Double, x3 As Double, y3 As Double, e1 As Double, x4 As Double, y4 As Double
x1 = Point(Line1(a)(1))(0): x2 = Point(Line1(a)(2))(0): y1 = Point(Line1(a)(1))(1): y2 = Point(Line1(a)(2))(1)
c1 = Dianju(x1, x2, y1, y2)
For i = 0 To b
  If Square(i)(0) = a Or Square(i)(1) = a Or Square(i)(2) = a Then
    Isline(IsEXit) = i
'    记载第i个三角形有与a重复的边
    IsEXit = IsEXit + 1
  End If
Next

Dim isg As Double
isg = 0
If IsEXit = 0 Then
For i = 0 To Count - 1
  x3 = Point(i)(0): y3 = Point(i)(1)
  a1 = Dianju(x1, x3, y1, y3): b1 = Dianju(x2, x3, y2, y3)
  If 2 * a1 * b1 <> 0 Then
  If Cosata > (a1 * a1 + b1 * b1 - c1 * c1) / (2 * a1 * b1) And (a1 * a1 + b1 * b1 - c1 * c1) / (2 * a1 * b1) <> -1 Then
    Cosata = (a1 * a1 + b1 * b1 - c1 * c1) / (2 * a1 * b1)
    BIjiaoAngel = i
  End If
  End If
Next
'找出角最大的点

ElseIf IsEXit = 1 Then
  e1 = Findc(Line1, Square_P, a, (Isline(IsEXit - 1)))
  x4 = Point(Square_P(Isline(IsEXit - 1))(e1))(0): y4 = Point(Square_P(Isline(IsEXit - 1))(e1))(1)
  For i = 0 To Count - 1
    x3 = Point(i)(0): y3 = Point(i)(1)
    If S(x1, y1, x2, y2, x3, y3, x4, y4) >= 0 Then
      isg = isg + 1
    Else
      a1 = Dianju(x1, x3, y1, y3): b1 = Dianju(x2, x3, y2, y3)
      If (2 * a1 * b1) <> 0 Then
        If Cosata > (a1 * a1 + b1 * b1 - c1 * c1) / (2 * a1 * b1) Then
          Cosata = (a1 * a1 + b1 * b1 - c1 * c1) / (2 * a1 * b1)
          BIjiaoAngel = i
        End If
      End If
    End If
  Next
  If isg = Count Then BIjiaoAngel = -1
ElseIf IsEXit = 2 Then
  BIjiaoAngel = -2
Else
BIjiaoAngel = -2
End If
End Function
Public Function Findc(Line1() As Variant, Square_P As Variant, a As Double, b As Double)
'第b个三角形存在与第a条边重复的边
Dim x1 As Double, x2 As Double, x3 As Double
x1 = Line1(a)(1): x2 = Line1(a)(2)
If x1 = Square_P(b)(0) Then
  If x2 = Square_P(b)(1) Then
    x3 = 2
  ElseIf x2 = Square_P(b)(2) Then
    x3 = 1
  End If
ElseIf x1 = Square_P(b)(1) Then
  If x2 = Square_P(b)(0) Then
    x3 = 2
  ElseIf x2 = Square_P(b)(2) Then
    x3 = 0
  End If
ElseIf x1 = Square_P(b)(2) Then
  If x2 = Square_P(b)(0) Then
    x3 = 1
  ElseIf x2 = Square_P(b)(1) Then
    x3 = 0
  End If
End If
Findc = x3
'Square_P(b)(x3)为对应点的点号
End Function
Public Function S(x1 As Double, y1 As Double, x2 As Double, y2 As Double, x3 As Double, y3 As Double, x4 As Double, y4 As Double)
'判断两点是否在一条直线同侧
Dim s1 As Double, s2 As Double
s1 = (x1 - x2) * (y3 - y2) - (y1 - y2) * (x3 - x2)
s2 = (x1 - x2) * (y4 - y2) - (y1 - y2) * (x4 - x2)
S = s1 * s2
End Function
Public Function layer_exist(layer_name As String) '判断是否存在图层
Dim i As Integer, tip As Integer
tip = 0
For i = 0 To ThisDrawing.Layers.Count - 1
    If (ThisDrawing.Layers.Item(i).Name = layer_name) Then
       tip = 1
       Exit For
    End If
Next i
End Function
Public Function Draw1(x As String)
Dim newlayer As AcadLayer
If (layer_exist(x)) Then
    newlayer = ThisDrawing.Layers.Item(x)
Else
    Set newlayer = ThisDrawing.Layers.Add(x)
End If
ThisDrawing.ActiveLayer = newlayer
End Function

Attribute VB_Name = "类1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Private Sub Class_Initialize()

End Sub
